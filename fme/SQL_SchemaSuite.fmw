FME workspace SQL_SchemaSuite.fmw

Parameters:
- dir =
- dir_2 =

Creator
    GEOMTYPE = Geometry Object
    NUM = 1
    CREATED -> FeatureReader [INITIATOR]
    CREATED -> FeatureReader_3 [INITIATOR]

Bookmark: PostgreSQL
Note: Lit les noms des fichers .sql dans le dossier
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(dir)
    FORMAT = PATH
    OUTPUT_FEATURES_DISPLAY = Schema and Data Features
    PATH_GLOB_PATTERN = *.sql
    PATH_NO_EMPTY_PROPERTIES = YES
    PATH_RECURSE_DIRECTORIES = NO
    PATH_RETRIEVE_FILE_PROPERTIES = NO
    PATH_TYPE = ANY
    PATH_USE_NON_STRING_ATTR = yes
    PATH -> FeatureReader_2 [INITIATOR]
Note: Lit le contenu des fichiers
FeatureReader_2
    ATTR_ACCUM_MODE = Only Use Result
    COMBINE_GEOM = Use Result
    DATASET = @Value(path_windows)
    FORMAT = TEXTLINE
    OUTPUT_FEATURES_DISPLAY = Schema and Data Features
    TEXTLINE_CREATE_FEATURE_TABLES_FROM_DATA = Yes
    TEXTLINE_ENCODING = windows-1252
    TEXTLINE_READ_WHOLE_FILE_AT_ONCE = YES
    <OTHER> -> AttributeExposer
AttributeExposer
    ATTR_LIST = text_line_data
    -> SQLExecutor [INITIATOR]
Note: Exécute le contenu SQL
SQLExecutor
    COMBINE_ATTRS = Result Attributes Only
    COMBINE_GEOM = Initiator Geometry Only
    DATASET = schemasuite_maville
    FORMAT = POSTGIS
    POSTGIS_CREATE_FEATURE_TABLES_FROM_DATA = Yes
    POSTGIS_DISABLE_COLLECTION_SPLITTING = yes
    POSTGIS_HOST = MonServeurPGSQL
    POSTGIS_PASSWORD =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
    POSTGIS_PORT = 5432
    POSTGIS_QUERY_FEATURE_TYPES_FOR_MERGE_FILTERS = Yes
    POSTGIS_READ_TIME_WITH_TIMEZONE = Yes
    POSTGIS_SSLMODE = prefer
    POSTGIS_USER_NAME = monuserpostgres
    POSTGIS_USE_TRUE_POSTGIS_TYPES = yes
    SQL_STATEMENT = @Value(text_line_data)

Bookmark: MSSQL
Note: Lit les noms des fichers .sql dans le dossier
FeatureReader_3
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Only Use Result
    COMBINE_GEOM = Use Result
    DATASET = $(dir_2)
    FORMAT = PATH
    OUTPUT_FEATURES_DISPLAY = Schema and Data Features
    PATH_GLOB_PATTERN = *.sql
    PATH_NO_EMPTY_PROPERTIES = YES
    PATH_RECURSE_DIRECTORIES = NO
    PATH_RETRIEVE_FILE_PROPERTIES = NO
    PATH_TYPE = ANY
    PATH_USE_NON_STRING_ATTR = yes
    PATH -> FeatureReader_4 [INITIATOR]
Note: Lit le contenu des fichiers
FeatureReader_4
    ATTR_ACCUM_MODE = Only Use Result
    COMBINE_GEOM = Use Result
    DATASET = @Value(path_windows)
    FORMAT = TEXTLINE
    OUTPUT_FEATURES_DISPLAY = Schema and Data Features
    TEXTLINE_CREATE_FEATURE_TABLES_FROM_DATA = Yes
    TEXTLINE_ENCODING = windows-1252
    TEXTLINE_READ_WHOLE_FILE_AT_ONCE = YES
    <OTHER> -> AttributeExposer_2
AttributeExposer_2
    ATTR_LIST = text_line_data
    -> SQLExecutor_5 [INITIATOR]
Note: Exécute le contenu SQL
SQLExecutor_5
    COMBINE_ATTRS = Result Attributes Only
    COMBINE_GEOM = Initiator Geometry Only
    DATASET = MaBaseSSE
    FORMAT = MSSQL_SPATIAL
    MSSQL_SPATIAL_APPLICATION_INTENT = ReadWrite
    MSSQL_SPATIAL_COMMAND_TIMEOUT = 30
    MSSQL_SPATIAL_CREATE_FEATURE_TABLES_FROM_DATA = Yes
    MSSQL_SPATIAL_ENCRYPT_CONNECTION = NO
    MSSQL_SPATIAL_MULTI_SUBNET_FAILOVER = NO
    MSSQL_SPATIAL_PASSWORD =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
    MSSQL_SPATIAL_QUERY_FEATURE_TYPES_FOR_MERGE_FILTERS = Yes
    MSSQL_SPATIAL_SERVER = MonServer
    MSSQL_SPATIAL_USER_NAME = test
    MSSQL_SPATIAL_USE_SSPI = NO
    SQL_STATEMENT = @Value(text_line_data)
